SUBAGENT-SHELL-MIB DEFINITIONS ::= BEGIN

IMPORTS
  MODULE-IDENTITY, enterprises FROM SNMPv2-SMI
  TimeStamp FROM SNMPv2-TC;

SUBAGENT-SHELL MODULE-IDENTITY
  LAST-UPDATED "200906251500Z"
  ORGANIZATION "Noname, Inc."
  CONTACT-INFO "abrikus@gmail.com"
  DESCRIPTION "SNMP SUBAGENT SHELL MIB"
  ::= { enterprises 777 }
  
  ssPollerInfo OBJECT IDENTIFIER ::= { SUBAGENT-SHELL 1 }
  functionsEntry OBJECT IDENTIFIER ::= { SUBAGENT-SHELL 100 }

  ssFunctionsCount  OBJECT-TYPE
    SYNTAX      INTEGER
    MAX-ACCESS  read-only
    STATUS      current
    DESCRIPTION
        "Number of executed functions"
    ::= { ssPollerInfo 1 }

  ssFunctionsSuccessCount  OBJECT-TYPE
    SYNTAX      INTEGER
    MAX-ACCESS  read-only
    STATUS      current
    DESCRIPTION
        "Number of successfully executed functions"
    ::= { ssPollerInfo 2 }

  ssFunctionsFailedCount  OBJECT-TYPE
    SYNTAX      INTEGER
    MAX-ACCESS  read-only
    STATUS      current
    DESCRIPTION
        "Number of failed functions"
    ::= { ssPollerInfo 3 }

  ssTimeStamp  OBJECT-TYPE
    SYNTAX      OCTET STRING
    MAX-ACCESS  read-only
    STATUS      current
    DESCRIPTION
        "Timestamp of last execution"
    ::= { ssPollerInfo 4 }
 
  ssTotalExecTime  OBJECT-TYPE
    SYNTAX      OCTET STRING
    MAX-ACCESS  read-only
    STATUS      current
    DESCRIPTION
        "Total execution time"
    ::= { ssPollerInfo 5 }

  ssMasterAgentPid OBJECT-TYPE
    SYNTAX      INTEGER
    MAX-ACCESS  read-only
    STATUS      current
    DESCRIPTION
        "Master Agent Process Id"
    ::= { ssPollerInfo 6 }

  ssPollerPid OBJECT-TYPE
    SYNTAX      INTEGER
    MAX-ACCESS  read-only
    STATUS      current
    DESCRIPTION
        "Poller Process Id"
    ::= { ssPollerInfo 7 }
END
