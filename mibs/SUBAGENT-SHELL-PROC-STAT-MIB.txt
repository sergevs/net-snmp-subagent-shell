SUBAGENT-SHELL-PROC-STAT-MIB DEFINITIONS ::= BEGIN

IMPORTS
  MODULE-IDENTITY, enterprises, Gauge32 FROM SNMPv2-SMI
  KBytes FROM HOST-RESOURCES-MIB
  functionsEntry FROM SUBAGENT-SHELL-MIB;

SUBAGENT-SHELL-PROC-STAT MODULE-IDENTITY
  LAST-UPDATED "200906251500Z"
  ORGANIZATION "Noname, Inc."
  CONTACT-INFO "abrikus@gmail.com"
  DESCRIPTION "SNMP SUBAGENT SHELL Processes statistics MIB"
  ::= { functionsEntry 3 }

  procTotal OBJECT-TYPE
    SYNTAX      Gauge32
    MAX-ACCESS  read-only
    STATUS      current
    DESCRIPTION "Total processes."
    ::= { SUBAGENT-SHELL-PROC-STAT 1 }

  procRunning OBJECT-TYPE
    SYNTAX      Gauge32
    MAX-ACCESS  read-only
    STATUS      current
    DESCRIPTION "Number of running processes."
    ::= { SUBAGENT-SHELL-PROC-STAT 2 }

  procSleeping  OBJECT-TYPE
    SYNTAX      Gauge32
    MAX-ACCESS  read-only
    STATUS      current
    DESCRIPTION "Number of sleeping processes."
    ::= { SUBAGENT-SHELL-PROC-STAT 3 }

  procStopped  OBJECT-TYPE
    SYNTAX      Gauge32
    MAX-ACCESS  read-only
    STATUS      current
    DESCRIPTION "Number of stopped processes."
    ::= { SUBAGENT-SHELL-PROC-STAT 4 }

  procZombie  OBJECT-TYPE
    SYNTAX      Gauge32
    MAX-ACCESS  read-only
    STATUS      current
    DESCRIPTION "Number of zombie processes."
    ::= { SUBAGENT-SHELL-PROC-STAT 5 }

  procUninterruptible  OBJECT-TYPE
    SYNTAX      Gauge32
    MAX-ACCESS  read-only
    STATUS      current
    DESCRIPTION "Number of uninterruptible processes."
    ::= { SUBAGENT-SHELL-PROC-STAT 6 }

  procInfoTable OBJECT-TYPE
    SYNTAX      SEQUENCE OF procInfoEntry
    MAX-ACCESS  not-accessible
    STATUS      current
    DESCRIPTION  "A list of apache status ."
    ::= { SUBAGENT-SHELL-PROC-STAT 8 }

  procInfoEntry OBJECT-TYPE
    SYNTAX      procInfoEntry
    MAX-ACCESS  not-accessible
    STATUS      current
    DESCRIPTION  "An entry containing information applicable to a process"
    INDEX      { procIndex }
    ::= { procInfoTable 1 }

  procInfoEntry ::=
    SEQUENCE {
        procVirtualMemory KBytes,
        procOpenFdCount   Gauge32, 
        procStartTime     INTEGER,
    }

  procVirtualMemory OBJECT-TYPE
    SYNTAX      KBytes
    MAX-ACCESS  read-only
    STATUS      current
    DESCRIPTION "Virtual memory of processes"
    ::= { procInfoEntry 1 }

  procOpenFdCount OBJECT-TYPE
    SYNTAX      Gauge32
    MAX-ACCESS  read-only
    STATUS      current
    DESCRIPTION "Number of open file descriptors"
    ::= { procInfoEntry 2 }

  procStartTime OBJECT-TYPE
    SYNTAX      INTEGER
    MAX-ACCESS  read-only
    STATUS      current
    DESCRIPTION "A process start timestamp (unixtime)"
    ::= { procInfoEntry 3 }

  procFuncExecTime OBJECT-TYPE
    SYNTAX      OCTET STRING
    MAX-ACCESS  read-only
    STATUS      current
    DESCRIPTION "Function execution time."
    ::= { SUBAGENT-SHELL-PROC-STAT 10 }

  procExecStatus OBJECT-TYPE
    SYNTAX      Integer32
    MAX-ACCESS  read-only
    STATUS      current
    DESCRIPTION "Exec code."
    ::= { SUBAGENT-SHELL-PROC-STAT 11 }


END
